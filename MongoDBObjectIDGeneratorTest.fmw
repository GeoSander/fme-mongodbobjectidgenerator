FME workspace MongoDBObjectIDGeneratorTest.fmw

Note: Feature with a bad mongodb_id
Creator
    GEOMTYPE = Geometry Object
    NUM = 1
    CREATED -> AttributeCopier
    CREATED -> MongoDBObjectIDGenerator
Note: Feature without a mongodb_id
Creator_2
    GEOMTYPE = Geometry Object
    NUM = 1
    CREATED -> AttributeCopier
    CREATED -> MongoDBObjectIDGenerator
Note: Feature with a valid mongodb_id
Creator_3
    GEOMTYPE = Geometry Object
    NUM = 1
    CREATED -> AttributeCopier
    CREATED -> MongoDBObjectIDGenerator
Note: Operation Mode: Validate / 2 features should be rejected, / the third should be valid.
MongoDBObjectIDGenerator
    __OPERATION_MODE = Validate
    -> StatisticsCalculator_2
    <Rejected> -> StatisticsCalculator
StatisticsCalculator_2
    COMPUTE_HISTOGRAM = NO
    STATS_ATTRS = mongodb_id
    PREPEND_ATTR_NAME_CHOICE = For multiple results only
    COUNT_ATTR = _count
    SUMMARY -> Tester_2
Tester_2
    TEST_CLAUSE = TEST @Value(_count) = 1
    TEST_DESCRIPTION = ""
    BOOL_OP = OR
    TEST_MODE = Automatic
    FAILED -> Terminator_2
Terminator_2
    MESSAGE = 1 Feature should pass validation
StatisticsCalculator
    COMPUTE_HISTOGRAM = NO
    STATS_ATTRS = mongodb_id
    PREPEND_ATTR_NAME_CHOICE = For multiple results only
    COUNT_ATTR = _count
    SUMMARY -> Tester
Tester
    TEST_CLAUSE = TEST @Value(_count) = 2
    TEST_DESCRIPTION = ""
    BOOL_OP = OR
    TEST_MODE = Automatic
    FAILED -> Terminator
Terminator
    MESSAGE = 2 Features should fail validation
Note: Store the original / ObjectID, if present
AttributeCopier
    ATTR_TABLE = COPY mongodb_id > original_id
    -> MongoDBObjectIDGenerator_2
Note: Operation Mode: Generate / All features should leave the / output port with a new ObjectID.
MongoDBObjectIDGenerator_2
    __OPERATION_MODE = Generate
    <Rejected> -> Terminator_3
Terminator_3
    MESSAGE = No features should be rejected
